# -*- coding: utf-8 -*-

# Macro by Mark1D
# Toggle between half and full rotation, with both
# plus and minus 180 degrees since sometimes your
# camera is on the bottom

import FreeCAD

# Filter to say if the part is revolutionary
def isRevolve(part):
    return part.TypeId == 'Part::Revolution' or part.TypeId == 'PartDesign::Revolution'

# Flips between three different revolve angles for the part, then returns the new angle
def toggleAngle(part):
    supportsNegative = part.TypeId == 'Part::Revolution'
    if part.Angle:
        if part.Angle == 360.0:
            part.Angle = 180.0
        elif part.Angle == 180.0 and supportsNegative:
            part.Angle = -180.0
        else:
            part.Angle = 360.0
        return part.Angle
    return 360.0

# Sets the revolve angle of a part
def setAngle(part, angle):
    if part.Angle:
        part.Angle = angle

# Toggles the first object in the list, then uses its new angle to set all the rest
def toggleAngleOfObjectList(list):
    angleToSetOtherObjectsTo = 0;
    for obj in filter(isRevolve, list):
        # App.Console.PrintMessage("Part: "+obj.Label+", "+obj.FullName+"\n")
        if angleToSetOtherObjectsTo == 0:
            angleToSetOtherObjectsTo = toggleAngle(obj)
        else:
            setAngle(obj, angleToSetOtherObjectsTo)

# Toggles the selected objects, or toggles all objects
if FreeCADGui.Selection.getSelection():
    toggleAngleOfObjectList(FreeCADGui.Selection.getSelection())
else:
    toggleAngleOfObjectList(App.ActiveDocument.Objects)

# All done! Enjoy your slices
