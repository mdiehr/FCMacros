#!/usr/bin/env python
# coding: utf-8

# Macro by Mark1D
# Calculates mass & moment of inertia for selected parts or all parts in the document

__Name__ = 'YoyoInfo'
__Comment__ = 'Yoyo stuff for making yoyos'
__Author__ = 'Mark1D'
__Version__ = '3.2.0'

import FreeCAD
import FreeCAD as app
import FreeCADGui as gui
from FreeCAD import Units, Matrix

from PySide import QtGui, QtCore
from PySide.QtGui import QApplication, QDialog, QMainWindow


# Preferences

# FreeCAD: Tools -> Edit Parameters, 2nd parameter of .GetX sets the default
MACRO_SETTINGS  = 'User parameter:BaseApp/Preferences/Macros/' + __Name__


GUI_FONT_SIZE = app.ParamGet('User parameter:BaseApp/Preferences/Editor').GetInt('FontSize', 10)
GUI_ICON_SIZE = app.ParamGet('User parameter:BaseApp/Preferences/General').GetInt('ToolbarIconSize', 24)



g_main_window = gui.getMainWindow()
g_font = g_main_window.font()
g_font.setPointSize(GUI_FONT_SIZE)
g_font_metrics = QtGui.QFontMetrics(g_font)
g_str_width = g_font_metrics.horizontalAdvance('_0_000e+00_')
g_icon_size = QtCore.QSize(GUI_ICON_SIZE, GUI_ICON_SIZE)
g_sel_user = []    # the user list of selected objects
g_sel = []    # the valid list of selected objects


class YoyoDock(QtGui.QDockWidget):

    def __init__(self):
        super().__init__()
        self.setAttribute(QtCore.Qt.WA_DeleteOnClose, True)    # free memory
        self.setLocale(QtCore.QLocale.English)
        self.child = YoyoWidget(self)
        self.setWidget(self.child)
        g_main_window.addDockWidget(QtCore.Qt.RightDockWidgetArea, self)



class YoyoWidget(QtGui.QWidget):
    """This is the widget which does almost all of the work.
    Widgets don't have close boxes, so closing is dealt with in
    CenterofmassWindow.
    """
    def __init__(self, parent):
        super().__init__(parent)
        self.setObjectName(__Name__)
        parent.setWindowTitle(__Name__ + ' ' + __Version__)
        parent.setFont(g_font)
        self.part_widgets = []
        self.doc = app.activeDocument()
        self.init_UI()
        self.on_push_button_recalculate()

    def init_UI(self):
        """Lay out the interactive elements"""
        self.layout = QtGui.QVBoxLayout(self)

        # Recalculate button
        button_recalculate = QtGui.QPushButton('Recalculate')
        button_recalculate.setToolTip('Recalculate Yoyo MMOI')
        button_recalculate.setIcon(QtGui.QIcon(':/icons/view-refresh.svg'))
        button_recalculate.setIconSize(g_icon_size)
        button_recalculate.clicked.connect(self.on_push_button_recalculate)

        # Parts dropdown
        self.create_parts_dropdown()

        # Calculated totals
        self.resultMass = create_label_line(self, 'mass')
        self.resultHalf = create_label_line(self, 'half mass')
        self.resultMMOI = create_label_line(self, 'MMOI')
        self.resultMMOIminor = create_label_line(self, 'MMOIminor')
        self.resultWidth = create_label_line(self, 'Width')
        self.resultDiameter = create_label_line(self, 'Diameter')
        self.resultCentroidX = create_label_line(self, 'centroidx')
        self.resultCentroidY = create_label_line(self, 'centroidy')

        layout_total = QtGui.QGridLayout()

        layout_total.addWidget(QtGui.QLabel('Mass'), 0, 0)
        layout_total.addWidget(self.resultMass, 0, 2)

        layout_total.addWidget(QtGui.QLabel('Half Mass'), 1, 0)
        layout_total.addWidget(self.resultHalf, 1, 2)

        layout_total.addWidget(QtGui.QLabel('MMOI Major'), 2, 0)
        layout_total.addWidget(self.resultMMOI, 2, 2)

        layout_total.addWidget(QtGui.QLabel('MMOI Minor'), 3, 0)
        layout_total.addWidget(self.resultMMOIminor, 3, 2)

        layout_total.addWidget(QtGui.QLabel('Width'), 4, 0)
        layout_total.addWidget(self.resultWidth, 4, 2)

        layout_total.addWidget(QtGui.QLabel('Diameter'), 5, 0)
        layout_total.addWidget(self.resultDiameter, 5, 2)

        layout_total.addWidget(QtGui.QLabel('Centroid (x)'), 6, 0)
        layout_total.addWidget(self.resultCentroidX, 6, 2)
        layout_total.addWidget(QtGui.QLabel('Centroid (y)'), 7, 0)
        layout_total.addWidget(self.resultCentroidY, 7, 2)

        self.box_totals = QtGui.QGroupBox(self.doc.Name)
        self.box_totals.setLayout(layout_total)

        # Yoyo parts
        self.partsLayout = QtGui.QGridLayout()

        # Headings
        self.partsLayout.addWidget(QtGui.QLabel('Label'), 0, 0)
        self.partsLayout.addWidget(QtGui.QLabel('Mass'), 0, 1)
        self.partsLayout.addWidget(QtGui.QLabel('MMOI'), 0, 2)

        self.box_parts = QtGui.QGroupBox()
        self.box_parts.setTitle('Parts')
        self.box_parts.setFlat(True)
        self.box_parts.setLayout(self.partsLayout)

        self.layout.addWidget(self.box_totals)
        self.layout.addWidget(button_recalculate)
        self.layout.addWidget(self.combo_parts)
        self.layout.addWidget(self.box_parts)
        self.layout.addStretch()
        pass

    def create_parts_dropdown(self):
        massOfPads = 0.30
        massOfBearing = 2.10
        massOfSEUltraLites = 2.50
        massOfSELego = 2.73
        massOfSESpikes = 3.20
        massOfSEBrassMarkmonts = 6.68
        massOfTopyoBearingAxle = 2.50
        massOfM85BearingAxle = 1.00

        self.parts_dict = {
            'C Bearing': massOfPads + massOfTopyoBearingAxle,
            'MR85 Bearing': massOfPads + massOfM85BearingAxle,
            'Side Effect - Ultra Lights': massOfPads + massOfBearing + massOfSEUltraLites,
            'Side Effect - Legos': massOfPads + massOfBearing + massOfSELego,
            'Side Effect - Spikes': massOfPads + massOfBearing + massOfSESpikes,
        }
        self.parts_mass = self.parts_dict.get('C Bearing')
        self.combo_parts = QtGui.QComboBox(toolTip='Select the parts for the bearing/pads')
        for key in self.parts_dict:
            self.combo_parts.addItem(key)
        self.combo_parts.currentIndexChanged.connect(self.on_parts_dropdown_changed)
        return self.combo_parts

    def on_parts_dropdown_changed(self, new_index):
        curr_text = self.combo_parts.currentText()
        self.parts_mass = self.parts_dict.get(curr_text)

    def on_push_button_recalculate(self):
        # Set doc name
        self.doc = app.activeDocument()
        self.box_totals.setTitle(self.doc.Name)

        # Instance of the class object
        yoyoAssembly = YoyoPartData()
        yoyoAssembly.parts = []

        # Runs for a selection or for all objects
        if FreeCADGui.Selection.getSelection():
            self.processList(yoyoAssembly, FreeCADGui.Selection.getSelection())
        else:
            self.processList(yoyoAssembly, App.ActiveDocument.Objects)

        # Outputs
        assembledMass = yoyoAssembly.yoyoMass * 2 + self.parts_mass
        mmoi = yoyoAssembly.mmoiMatrix[0]
        self.resultHalf.setText('{:12.6} g'.format(yoyoAssembly.yoyoMass))
        self.resultMass.setText('{:12.6} g'.format(assembledMass))
        self.resultMMOI.setText('{:12.6}'.format(mmoi))
        self.resultMMOIminor.setText('{:12.6}'.format(yoyoAssembly.mmoiMatrix[1]))

        bbox = yoyoAssembly.getBoundingBox()
        width:float = float(bbox[1]-bbox[0])
        half_width:float = float(bbox[1]) # used for centroid, bbox[1] is xmax
        diameter:float = float(bbox[3]-bbox[2])
        radius:float = float(bbox[3])
        self.resultWidth.setText('{:6.4} mm'.format(float(width)))
        self.resultDiameter.setText('{:6.4} mm'.format(float(diameter)))

        percentWeightToWidth:float = float(100 * yoyoAssembly.centroid / half_width)
        percentWeightToRadius:float = 100.0 * mmoi / (yoyoAssembly.yoyoMass * radius * radius)
        self.resultCentroidX.setText('{:6.4} %'.format(percentWeightToWidth))
        self.resultCentroidY.setText('{:6.4} %'.format(float(percentWeightToRadius)))

        # Parts list
        if len(self.part_widgets) > 0:
            self.clear_parts_layout()
        index = 1
        for part in yoyoAssembly.parts:
            self.part_widgets.append(PartWidget(parent=self, part=part, index=index))
            index = index + 1
        pass

    def clear_parts_layout(self):
        for part in self.part_widgets:
            part.cleanup()
            del part
        self.part_widgets = []
        pass

    # Looks at all the objects in the document
    def processList(self, yoyo, objList):
        for obj in filter(isPartSolid, objList):
            yoyo.addPart(obj)

class PartWidget():
    """Rows in parts area"""
    def __init__(self, *, parent, part, index):
        self.parent = parent
        self.part = part
        self.result01 = QtGui.QLabel(part['label'])
        self.result02 = QtGui.QLabel('{:10.4} g'.format(part['mass']))
        self.result03 = QtGui.QLabel('{:10.6}'.format(part['mmoi']))

        self.parent.partsLayout.addWidget(self.result01, index, 0)
        self.parent.partsLayout.addWidget(self.result02, index, 1)
        self.parent.partsLayout.addWidget(self.result03, index, 2)

    def cleanup(self):
        self.result01.deleteLater()
        self.result02.deleteLater()
        self.result03.deleteLater()

class YoyoPartData:
    yoyoMass = 0.0

    parts = []  # parts with density, stored as convenient dicts of summary info
    partFeatures = [] # everything

    mmoiMatrix = [0,0,0] # only XX, YY, ZZ

    centroid = 0.00 # only along x axis, for one half

    unitMass = 1.00 # gram
    unitLength = 1.00 # mm
    unitVolume = 1.00 # mm3

    massOfPads = 0.30
    massOfBearing = 2.10
    massOfSEUltraLites = 2.50
    massOfSELego = 2.73
    massOfSESpikes = 3.20
    massOfSEBrassMarkmonts = 6.68
    massOfTopyoBearingAxle = 2.50
    massOfM85BearingAxle = 1.00
    massOfBearingPadsAxle = massOfPads + massOfTopyoBearingAxle

    formatString = "{:10.2f}"

    def __init__(self):
        self.parts = []
        self.partFeatures = []
        self.mmoiMatrix = [0,0,0]

    def addPart(self, part):
        # App.Console.PrintMessage(part.Label + " ("+part.FullName+")\n")
        partDensity = 0.0
        self.partFeatures.append(part)
        try:
            labelParts = part.Label.split()
            labelDensity = labelParts[len(labelParts)-1]
            partDensity = float(labelDensity)
        except:
            # App.Console.PrintMessage("Couldn't read density from: '"+part.Label+"', skipping this part\n")
            return



        partVolume = part.Shape.Volume
        partMass = partVolume * partDensity / 1000.0
        partMMOI = self.addMOI(part, partDensity)
        mx = abs(part.Shape.CenterOfMass[0]);
        self.addCentroid(mx, partMass) # Part of centroid
        self.yoyoMass = self.yoyoMass + partMass


        # Combine all data and append to parts list
        partData = { 'label': part.Label,
                'mass': partMass,
                'density': partDensity,
                'volume': partVolume,
                'mmoi': partMMOI,
                'mx': mx,
                }
        self.parts.append(partData)

        # App.Console.PrintMessage("\tDensity: "+self.formatString.format(partDensity)+"\n")
        # App.Console.PrintMessage("\tMass:    "+self.formatString.format(partMass)+" g\n")
        # self.printData();

    def getBoundingBox(self):
        boxes = [pf.Shape.BoundBox for pf in self.partFeatures]

        XMin = 0;
        XMax = 0;
        YMin = 0;
        YMax = 0;
        ZMin = 0;
        ZMax = 0;

        for box in boxes:
            XMin = min(XMin, box.XMin)
            XMax = max(XMax, box.XMax)
            YMin = min(YMin, box.YMin)
            YMax = max(YMax, box.YMax)
            ZMin = min(ZMin, box.ZMin)
            ZMax = max(ZMax, box.ZMax)
        return (XMin, XMax, YMin, YMax, ZMin, ZMax)

    def addCentroid(self, mx, partMass):
        if partMass <= 0.0:
            return
        self.centroid = (self.centroid * self.yoyoMass + mx * partMass) / (self.yoyoMass + partMass);

    def addMOI(self, part, partDensity):
        myMajor = 0
        scale = self.unitLength**5 * partDensity * self.unitMass * (1.0 / (self.unitVolume * 1000.0))
        # A part can have multiple solids
        for solid in part.Shape.Solids:
            Icm = solid.MatrixOfInertia
            cm = solid.CenterOfMass
            m = solid.Volume * partDensity * self.unitMass / (self.unitVolume * 1000.0)
            d = abs(cm.x) # assume X axis is axis of rotation

            # Parallel axis theorem: I = Icm + md^2
            md2 = m * d**2 
            # Apply only to y/z axis, since X is primary axis of rotation
            self.mmoiMatrix[0] += Icm.A[0] * scale
            self.mmoiMatrix[1] += Icm.A[5] * scale + md2
            self.mmoiMatrix[2] += Icm.A[10] * scale + md2
            myMajor += Icm.A[0] * scale

        return myMajor



# Utility method
def create_label_line(parent, name):
    line = QtGui.QLineEdit(parent)
    line.setObjectName(name)
    line.setReadOnly(True)
    return line

# Filter to say if the part type should be included in the calculations
def isPartSolid(part):
    if "Part::" in part.TypeId or "PartDesign::" in part.TypeId:
        # App.Console.PrintMessage('Checking part ' + part.TypeId + ' ' + part.Label + ' ' + part.FullName + '\n')
        if part.Shape:
            if part.Shape.Volume:
                return part.Shape.Volume > 0
    return False;

def error_message(msg):
    app.Console.PrintError(msg + '\n')
    QtGui.QMessageBox.critical(g_main_window, 'Error', msg)

if __name__ == '__main__':
    if not app.activeDocument():
        error_message('Open a document first.')
    else:
        print('Loading ' + __Name__ + ' ' + __Version__ + ' ...')
        gui.updateGui()
        myWidget = YoyoDock()
